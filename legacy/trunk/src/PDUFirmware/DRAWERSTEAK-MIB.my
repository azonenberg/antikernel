DRAWERSTEAK-MIB DEFINITIONS ::= BEGIN

--
-- @file
-- @author Andrew D. Zonenberg
-- @brief Root MIB for drawersteak stuff
-- 

	IMPORTS
		MODULE-IDENTITY, enterprises FROM SNMPv2-SMI;

	drawersteak MODULE-IDENTITY
		LAST-UPDATED "201310021200Z"
		ORGANIZATION "Andrew Zonenberg"
		CONTACT-INFO "azonenberg@drawersteak.com"
		DESCRIPTION "Andrew Zonenberg and DrawerSteak Research"
	::= { enterprises 42453}
	
	-- Device identifiers
	-- Each device has a unique OID within this node.
	devids OBJECT IDENTIFIER ::= {drawersteak 1}
	
	-- Per-device MIBs are 2 and up
	
END
